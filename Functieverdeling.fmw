FME workspace Functieverdeling.fmw
Title: GSICalculator
Description: Berekent voor de gemeente Rotterdam de FSI per CBS-buurt, CBS-wijk en CBS-gemeente met GSI = oppervlakte(gebouwfopotprint) / oppervlakte (land).
History: 26-3-2018,Jeroen de Vries,v1.0

Parameters:
- P_BRON_CBS_WYKBRT_WFS = https://geodata.nationaalgeoregister.nl/wijkenbuurten2017/wfs?   # Source WFS (Web Feature Service) URL
- P_BRON_BGT_FGDB = K:\GEODATA\Basisdata\BGT\Data\GDB\BGT_Gemeente\BGT_Gemeente.gdb   # File Geodatabase
- P_BRON_BGT_WHERE = NIVO = 0 AND KLASSE_IMG NOT IN ('Ongeclassificeerd object','Vegetatieobject','Weginrichtingselement')   # WHERE Clause
- P_DOEL_GPKG = K:\GEODATA\Kennisloods\Data\Functieverdeling\Functieverdeling.gpkg   # GeoPackage File
- P_DOEL_FGDB = K:\GEODATA\Kennisloods\Data\Functieverdeling\Functieverdeling.gdb   # File Geodatabase
- P_COORDSYS = EPSG:28992   # Coordinate System
- P_MINX = 55500   # Minimum X
- P_MINY = 428647   # Minimum Y
- P_MAXX = 101040   # Maximum X
- P_MAXY = 447000   # Maximum Y
- P_PEILDATUM = 2017   # " " Attribute Value
- P_LOGBESTAND = $(FME_MF_DIR)log\Functieverdeling.log   # Log File

Readers:
- WFS_1: WFS from $(P_BRON_CBS_WYKBRT_WFS) in $(P_COORDSYS)
- WFS_2: WFS from $(P_BRON_CBS_WYKBRT_WFS) in $(P_COORDSYS)
- WFS_3: WFS from $(P_BRON_CBS_WYKBRT_WFS) in $(P_COORDSYS)
- GEODATABASE_FILE_1: GEODATABASE_FILE from $(P_BRON_BGT_FGDB) in $(P_COORDSYS)

Writers:
- GEOPACKAGE_1: GEOPACKAGE to $(P_DOEL_GPKG) in $(P_COORDSYS)
- GEODATABASE_FILE_2: GEODATABASE_FILE to $(P_DOEL_FGDB) in $(P_COORDSYS)

Note: TE DOEN / - Update bestaande gegevens: / - toevoegen nieuwe record per aandachtsgebied met ind_actueel = 1 / - bijwerken oude records: ind_actueel wordt 0 / - directe mutatie ArcGIS Online / ESRI Enterprise / - automatisch berekenen peildatum (nu nog hard in AttributeCreator_peildatum)
AttributeFilter_BGT_KLASSE_IMG
    ATTR_VALUES = <Empty>,<Missing>,<Null>,<Unfiltered>,Begroeid terreindeel,Onbegroeid terreindeel,Overig bouwwerk,Gebouwinstallatie,Pand,Kunstwerkdeel,Scheiding,Ondersteunend waterdeel,Waterdeel,Ondersteunend wegdeel,Overbruggingsdeel,Wegdeel
    ATTR_NAME = KLASSE_IMG
    Begroeid terreindeel -> AttributeCreator_Groen
    Onbegroeid terreindeel -> AttributeCreator_Bebouwing
    Overig bouwwerk -> AttributeCreator_Bebouwing
    Gebouwinstallatie -> AttributeCreator_Bebouwing
    Pand -> AttributeCreator_Bebouwing
    Kunstwerkdeel -> AttributeCreator_Bebouwing
    Scheiding -> AttributeCreator_Bebouwing
    Ondersteunend waterdeel -> AttributeCreator_Water
    Waterdeel -> AttributeCreator_Water
    Ondersteunend wegdeel -> AttributeCreator_Infra_Auto
    Overbruggingsdeel -> AttributeCreator_Infra_Overig
    Wegdeel -> AttributeFilter_BGT_Wegdeel_FUNCTIE
AttributeCreator_Groen
    ATTR_TABLE:
      SET_TO _classificatie = groen
      SET_TO _oppervlaktedeler = 1
    -> AttributeKeeper_classificatie
AttributeCreator_Bebouwing
    ATTR_TABLE:
      SET_TO _classificatie = bebouwing
      SET_TO _oppervlaktedeler = 1
    -> AttributeKeeper_classificatie
AttributeCreator_Water
    ATTR_TABLE:
      SET_TO _classificatie = water
      SET_TO _oppervlaktedeler = 1
    -> AttributeKeeper_classificatie
AttributeFilter_BGT_Wegdeel_FUNCTIE
    ATTR_VALUES = <Empty>,<Missing>,<Null>,<Unfiltered>,ruiterpad,transitie,inrit,rijbaan autosnelweg,rijbaan autoweg,rijbaan lokale weg,rijbaan regionale weg,overweg,spoorbaan,OV-baan,fietspad,voetgangersgebied,voetpad,voetpad op trap,parkeervlak,baan voor vliegverkeer
    ATTR_NAME = FUNCTIE
    ruiterpad -> AttributeCreator_Infra_Overig
    transitie -> AttributeCreator_Infra_Overig
    inrit -> AttributeCreator_Infra_Auto
    rijbaan autosnelweg -> AttributeCreator_Infra_Auto
    rijbaan autoweg -> AttributeCreator_Infra_Auto
    rijbaan lokale weg -> AttributeCreator_Infra_Auto
    rijbaan regionale weg -> AttributeCreator_Infra_Auto_helft
    rijbaan regionale weg -> AttributeCreator_Infra_OV_helft
    overweg -> AttributeCreator_Infra_OV
    spoorbaan -> AttributeCreator_Infra_OV
    OV-baan -> AttributeCreator_Infra_OV
    fietspad -> AttributeCreator_Infra_Fiets
    voetgangersgebied -> AttributeCreator_Infra_Voetgangers
    voetpad -> AttributeCreator_Infra_Voetgangers
    voetpad op trap -> AttributeCreator_Infra_Voetgangers
    parkeervlak -> AttributeCreator_Infra_Parkeervlak
    baan voor vliegverkeer -> AttributeCreator_Infra_Vliegverkeer
AttributeCreator_Infra_Overig
    ATTR_TABLE:
      SET_TO _classificatie = infra_overig
      SET_TO _oppervlaktedeler = 1
    -> AttributeKeeper_classificatie
AttributeCreator_Infra_Auto
    ATTR_TABLE:
      SET_TO _classificatie = infra_auto
      SET_TO _oppervlaktedeler = 1
    -> AttributeKeeper_classificatie
AttributeCreator_Infra_Auto_helft
    ATTR_TABLE:
      SET_TO _classificatie = infra_auto
      SET_TO _oppervlaktedeler = 2
    -> AttributeKeeper_classificatie
AttributeCreator_Infra_OV_helft
    ATTR_TABLE:
      SET_TO _classificatie = infra_ov
      SET_TO _oppervlaktedeler = 2
    -> AttributeKeeper_classificatie
AttributeCreator_Infra_OV
    ATTR_TABLE:
      SET_TO _classificatie = infra_ov
      SET_TO _oppervlaktedeler = 1
    -> AttributeKeeper_classificatie
AttributeCreator_Infra_Fiets
    ATTR_TABLE:
      SET_TO _classificatie = infra_fiets
      SET_TO _oppervlaktedeler = 1
    -> AttributeKeeper_classificatie
AttributeCreator_Infra_Voetgangers
    ATTR_TABLE:
      SET_TO _classificatie = infra_voetgangers
      SET_TO _oppervlaktedeler = 1
    -> AttributeKeeper_classificatie
AttributeCreator_Infra_Parkeervlak
    ATTR_TABLE:
      SET_TO _classificatie = infra_parkeervlak
      SET_TO _oppervlaktedeler = 1
    -> AttributeKeeper_classificatie
AttributeCreator_Infra_Vliegverkeer
    ATTR_TABLE:
      SET_TO _classificatie = infra_vliegverkeer
      SET_TO _oppervlaktedeler = 1
    -> AttributeKeeper_classificatie
AttributeKeeper_classificatie
    KEEP_ATTRS = _classificatie,_oppervlaktedeler
    -> Clipper_BGT_CBSbuurt [CLIPPEE]
Note: filteren: gebied in Rotterdam en / met een oppervlakte > 0 ha
Tester_4
    TEST_MODE = Automatic
    TEST_CLAUSE:
      TEST @Value(gemeentecode) = GM0599
      TEST @Value(oppervlakte_land_in_ha) > 0
    TEST_DESCRIPTION = ""
    BOOL_OP = AND
    PASSED -> AttributeManager_3
AttributeManager_3
    ATTR_TABLE:
      REMOVE gml_parent_id
      REMOVE gml_parent_property
      REMOVE gml_id
      REMOVE aantal_inwoners
      REMOVE aantal_inwoners.xsi_nil
      REMOVE mannen
      REMOVE mannen.xsi_nil
      REMOVE vrouwen
      REMOVE vrouwen.xsi_nil
      REMOVE aantal_huishoudens
      REMOVE aantal_huishoudens.xsi_nil
      REMOVE bevolkingsdichtheid_inwoners_per_km2
      REMOVE bevolkingsdichtheid_inwoners_per_km2.xsi_nil
      REMOVE dekkingspercentage
      REMOVE dekkingspercentage.xsi_nil
      REMOVE gemiddelde_huishoudsgrootte
      REMOVE gemiddelde_huishoudsgrootte.xsi_nil
      RENAME_SET_VALUE gemeentecode > CBS_gemeentecode
      REMOVE gemeentecode.xsi_nil
      RENAME_SET_VALUE gemeentenaam > CBS_gemeentenaam
      REMOVE gemeentenaam.xsi_nil
      REMOVE omgevingsadressendichtheid
      REMOVE omgevingsadressendichtheid.xsi_nil
      REMOVE oppervlakte_land_in_ha
      REMOVE oppervlakte_land_in_ha.xsi_nil
      REMOVE oppervlakte_totaal_in_ha
      REMOVE oppervlakte_totaal_in_ha.xsi_nil
      REMOVE oppervlakte_water_in_ha
      REMOVE oppervlakte_water_in_ha.xsi_nil
      REMOVE percentage_personen_0_tot_15_jaar
      REMOVE percentage_personen_0_tot_15_jaar.xsi_nil
      REMOVE percentage_personen_15_tot_25_jaar
      REMOVE percentage_personen_15_tot_25_jaar.xsi_nil
      REMOVE percentage_personen_25_tot_45_jaar
      REMOVE percentage_personen_25_tot_45_jaar.xsi_nil
      REMOVE percentage_personen_45_tot_65_jaar
      REMOVE percentage_personen_45_tot_65_jaar.xsi_nil
      REMOVE percentage_personen_65_jaar_en_ouder
      REMOVE percentage_personen_65_jaar_en_ouder.xsi_nil
      REMOVE percentage_uit_nederlandse_antillen_en_aruba
      REMOVE percentage_uit_nederlandse_antillen_en_aruba.xsi_nil
      REMOVE percentage_eenpersoonshuishoudens
      REMOVE percentage_eenpersoonshuishoudens.xsi_nil
      REMOVE percentage_gehuwd
      REMOVE percentage_gehuwd.xsi_nil
      REMOVE percentage_gescheid
      REMOVE percentage_gescheid.xsi_nil
      REMOVE percentage_huishoudens_met_kinderen
      REMOVE percentage_huishoudens_met_kinderen.xsi_nil
      REMOVE percentage_huishoudens_zonder_kinderen
      REMOVE percentage_huishoudens_zonder_kinderen.xsi_nil
      REMOVE percentage_uit_marokko
      REMOVE percentage_uit_marokko.xsi_nil
      REMOVE percentage_niet_westerse_allochtonen
      REMOVE percentage_niet_westerse_allochtonen.xsi_nil
      REMOVE percentage_ongehuwd
      REMOVE percentage_ongehuwd.xsi_nil
      REMOVE percentage_overige_niet_westerse_allochtonen
      REMOVE percentage_overige_niet_westerse_allochtonen.xsi_nil
      REMOVE percentage_uit_suriname
      REMOVE percentage_uit_suriname.xsi_nil
      REMOVE percentage_uit_turkije
      REMOVE percentage_uit_turkije.xsi_nil
      REMOVE percentage_verweduwd
      REMOVE percentage_verweduwd.xsi_nil
      REMOVE percentage_westerse_allochtonen
      REMOVE percentage_westerse_allochtonen.xsi_nil
      REMOVE meest_voorkomende_postcode
      REMOVE meest_voorkomende_postcode.xsi_nil
      REMOVE stedelijkheid_adressen_per_km2
      REMOVE stedelijkheid_adressen_per_km2.xsi_nil
      REMOVE water
      REMOVE water.xsi_nil
      REMOVE geom
      REMOVE indelingswijziging_wijken_en_buurten_indicator
      REMOVE indelingswijziging_wijken_en_buurten_indicator.xsi_nil
      RENAME_SET_VALUE wijkcode > CBS_wijkcode
      REMOVE wijkcode.xsi_nil
      RENAME_SET_VALUE buurtcode > CBS_buurtcode
      REMOVE buurtcode.xsi_nil
      RENAME_SET_VALUE buurtnaam > CBS_buurtnaam
      REMOVE buurtnaam.xsi_nil
    -> AreaCalculator_CBSbuurt
    -> Clipper_BGT_CBSbuurt [CLIPPER]
Note: minx 55500 / miny 428647 / maxx 101040 / maxy 447000
Clipper_BGT_CBSbuurt
    PRESERVE_CLIPPEE_EXTENTS = No
    ATTR_CONFLICT_RES = Use Clippee
    MISSING_VAL_MODE = Compute
    VAL_SOURCE = Clippee Only
    ATTR_ACCUM_MODE = Merge Clipper
    CLIPPED_ATTR = _clipped
    MEASURE_TYPE = Continuous
    CREATE_AGGREGATES = Yes
    CLIP_TYPE = Multiple Clippers
    LINES_AS_SEGMENTS = No
    BOUNDARY_CASES = Treat as Inside
    INSIDE -> AreaCalculator
    <REJECTED> -> Junction_11
AreaCalculator
    AREA_TYPE = Plane Area
    MULT = 1/@Value(_oppervlaktedeler)
    AREA_ATTR = _area
    -> AttributeFilter
    <REJECTED> -> Junction_13
AttributeFilter
    ATTR_VALUES = <Empty>,<Missing>,<Null>,<Unfiltered>,groen,bebouwing,water,infra_overig,infra_auto,infra_ov,infra_fiets,infra_voetgangers,infra_parkeervlak,infra_vliegverkeer
    ATTR_NAME = _classificatie
    groen -> AttributeCreator_opp_groen
    bebouwing -> AttributeCreator_opp_bebouwing
    water -> AttributeCreator_opp_water
    infra_overig -> AttributeCreator_opp_infra_overig
    infra_auto -> AttributeCreator_opp_infra_auto
    infra_ov -> AttributeCreator_groen_opp_ov
    infra_fiets -> AttributeCreator_groen_opp_fiets
    infra_voetgangers -> AttributeCreator_groen_opp_voetgangers
    infra_parkeervlak -> AttributeCreator_groen_opp_parkeervlak
    infra_vliegverkeer -> AttributeCreator_groen_opp_vliegverkeer
AttributeCreator_opp_groen
    ATTR_TABLE = SET_TO opp_groen = @Value(_area)
    -> StatisticsCalculator
AttributeCreator_opp_bebouwing
    ATTR_TABLE = SET_TO opp_bebouwing = @Value(_area)
    -> StatisticsCalculator
AttributeCreator_opp_water
    ATTR_TABLE = SET_TO opp_water = @Value(_area)
    -> StatisticsCalculator
AttributeCreator_opp_infra_overig
    ATTR_TABLE = SET_TO opp_infra_overig = @Value(_area)
    -> StatisticsCalculator
AttributeCreator_opp_infra_auto
    ATTR_TABLE = SET_TO opp_infra_auto = @Value(_area)
    -> StatisticsCalculator
AttributeCreator_groen_opp_ov
    ATTR_TABLE = SET_TO opp_infra_ov = @Value(_area)
    -> StatisticsCalculator
AttributeCreator_groen_opp_fiets
    ATTR_TABLE = SET_TO opp_infra_fiets = @Value(_area)
    -> StatisticsCalculator
AttributeCreator_groen_opp_voetgangers
    ATTR_TABLE = SET_TO opp_infra_voetgangers = @Value(_area)
    -> StatisticsCalculator
AttributeCreator_groen_opp_parkeervlak
    ATTR_TABLE = SET_TO opp_infra_parkeervlak = @Value(_area)
    -> StatisticsCalculator
AttributeCreator_groen_opp_vliegverkeer
    ATTR_TABLE = SET_TO opp_infra_vliegverkeer = @Value(_area)
    -> StatisticsCalculator
StatisticsCalculator
    COMPUTE_HISTOGRAM = NO
    PREPEND_ATTR_NAME_CHOICE = For multiple results only
    SUM_ATTR = _sum
    STATS_ATTRS = opp_groen opp_infra_auto opp_infra_fiets opp_infra_vliegverkeer opp_water opp_bebouwing opp_infra_ov opp_infra_overig opp_infra_parkeervlak opp_infra_voetgangers
    GROUP_BY = CBS_buurtcode
    SUMMARY -> FeatureMerger_3 [SUPPLIER]
Junction_13
    -> Junction_14
Junction_14
    -> _Rejected_
Junction_11
    -> Junction_12
Junction_12
    -> _Rejected_
AreaCalculator_CBSbuurt
    AREA_TYPE = Plane Area
    MULT = 1
    AREA_ATTR = _area
    -> FeatureMerger_3 [REQUESTOR]
    <REJECTED> -> Junction_9
FeatureMerger_3
    SUPPLIERS_FIRST = No
    PROCESS_DUPS = No
    ATTR_CONFLICT_RES = Use Requestor
    REJECT_NULL_MISSING_KEYS = No
    ATTR_ACCUM_MODE = Merge Supplier
    JOIN_KEYS = @Value(CBS_buurtcode) @Value(CBS_buurtcode) AUTO
    MERGE_TYPE = Attributes Only
    IGNORE_NULLS = No
    MERGED -> Aggregator_Pand_Wijk
    MERGED -> PercenterenEnAfronden_CBSbuurt [In]
    <REJECTED> -> Junction_17
PercenterenEnAfronden_CBSbuurt
    OPP_INFRA_PARKEERVLAK._SUM = @Value(opp_infra_parkeervlak._sum)
    OPP_INFRA_OVERIG._SUM = @Value(opp_infra_overig._sum)
    OPP_INFRA_OV._SUM = @Value(opp_infra_ov._sum)
    OPP_INFRA_AUTO._SUM = @Value(opp_infra_auto._sum)
    _AREA = @Value(_area)
    OPP_WATER._SUM = @Value(opp_water._sum)
    OPP_INFRA_VLIEGVERKEER._SUM = @Value(opp_infra_vliegverkeer._sum)
    OPP_BEBOUWING._SUM = @Value(opp_bebouwing._sum)
    OPP_INFRA_FIETS._SUM = @Value(opp_infra_fiets._sum)
    OPP_INFRA_VOETGANGERS._SUM = @Value(opp_infra_voetgangers._sum)
    OPP_GROEN._SUM = @Value(opp_groen._sum)
    Uit -> AttributeCreator_peildatum_Buurt
    <Rejected> -> Junction_15
Junction_15
    -> Junction_16
Junction_16
    -> _Rejected_
Junction_17
    -> Junction_18
Junction_18
    -> _Rejected_
Note: Per CBSWijk sommeren / van de oppervlaktes.
Aggregator_Pand_Wijk
    ACCUM_ATTRS_NAME = Drop Incoming Attributes
    SUM = opp_infra_fiets._sum opp_infra_overig._sum opp_infra_vliegverkeer._sum opp_infra_voetgangers._sum _area opp_infra_parkeervlak._sum opp_groen._sum opp_infra_ov._sum opp_infra_auto._sum opp_water._sum opp_bebouwing._sum
    MODE = Attributes Only
    SEP = ,
    GROUP_BY = CBS_wijkcode CBS_gemeentecode
    ORDERED = No
    AGGREGATE -> Aggregator_Pand_Gemeente
    AGGREGATE -> FeatureMerger_CBSwijk [SUPPLIER]
Note: Per CBSGemeente sommeren / van de oppervlaktes.
Aggregator_Pand_Gemeente
    ACCUM_ATTRS_NAME = Drop Incoming Attributes
    SUM = opp_infra_fiets._sum opp_infra_overig._sum opp_infra_vliegverkeer._sum opp_infra_voetgangers._sum _area opp_infra_parkeervlak._sum opp_groen._sum opp_infra_ov._sum opp_infra_auto._sum opp_water._sum opp_bebouwing._sum
    MODE = Attributes Only
    SEP = ,
    GROUP_BY = CBS_gemeentecode
    ORDERED = No
    AGGREGATE -> FeatureMerger_CBSgemeente [SUPPLIER]
Junction_9
    -> Junction_10
Junction_10
    -> _Rejected_
Tester_3
    TEST_MODE = Automatic
    TEST_CLAUSE:
      TEST @Value(gemeentecode) = GM0599
      TEST @Value(oppervlakte_land_in_ha) > 0
    TEST_DESCRIPTION = ""
    BOOL_OP = AND
    PASSED -> AttributeManager_2
AttributeManager_2
    ATTR_TABLE:
      REMOVE gml_parent_id
      REMOVE gml_parent_property
      REMOVE gml_id
      REMOVE aantal_inwoners
      REMOVE aantal_inwoners.xsi_nil
      REMOVE mannen
      REMOVE mannen.xsi_nil
      REMOVE vrouwen
      REMOVE vrouwen.xsi_nil
      REMOVE aantal_huishoudens
      REMOVE aantal_huishoudens.xsi_nil
      REMOVE bevolkingsdichtheid_inwoners_per_km2
      REMOVE bevolkingsdichtheid_inwoners_per_km2.xsi_nil
      REMOVE dekkingspercentage
      REMOVE dekkingspercentage.xsi_nil
      REMOVE gemiddelde_huishoudsgrootte
      REMOVE gemiddelde_huishoudsgrootte.xsi_nil
      RENAME_SET_VALUE gemeentecode > CBS_gemeentecode
      REMOVE gemeentecode.xsi_nil
      RENAME_SET_VALUE gemeentenaam > CBS_gemeentenaam
      REMOVE gemeentenaam.xsi_nil
      REMOVE omgevingsadressendichtheid
      REMOVE omgevingsadressendichtheid.xsi_nil
      REMOVE oppervlakte_land_in_ha
      REMOVE oppervlakte_land_in_ha.xsi_nil
      REMOVE oppervlakte_totaal_in_ha
      REMOVE oppervlakte_totaal_in_ha.xsi_nil
      REMOVE oppervlakte_water_in_ha
      REMOVE oppervlakte_water_in_ha.xsi_nil
      REMOVE percentage_personen_0_tot_15_jaar
      REMOVE percentage_personen_0_tot_15_jaar.xsi_nil
      REMOVE percentage_personen_15_tot_25_jaar
      REMOVE percentage_personen_15_tot_25_jaar.xsi_nil
      REMOVE percentage_personen_25_tot_45_jaar
      REMOVE percentage_personen_25_tot_45_jaar.xsi_nil
      REMOVE percentage_personen_45_tot_65_jaar
      REMOVE percentage_personen_45_tot_65_jaar.xsi_nil
      REMOVE percentage_personen_65_jaar_en_ouder
      REMOVE percentage_personen_65_jaar_en_ouder.xsi_nil
      REMOVE percentage_uit_nederlandse_antillen_en_aruba
      REMOVE percentage_uit_nederlandse_antillen_en_aruba.xsi_nil
      REMOVE percentage_eenpersoonshuishoudens
      REMOVE percentage_eenpersoonshuishoudens.xsi_nil
      REMOVE percentage_gehuwd
      REMOVE percentage_gehuwd.xsi_nil
      REMOVE percentage_gescheid
      REMOVE percentage_gescheid.xsi_nil
      REMOVE percentage_huishoudens_met_kinderen
      REMOVE percentage_huishoudens_met_kinderen.xsi_nil
      REMOVE percentage_huishoudens_zonder_kinderen
      REMOVE percentage_huishoudens_zonder_kinderen.xsi_nil
      REMOVE percentage_uit_marokko
      REMOVE percentage_uit_marokko.xsi_nil
      REMOVE percentage_niet_westerse_allochtonen
      REMOVE percentage_niet_westerse_allochtonen.xsi_nil
      REMOVE percentage_ongehuwd
      REMOVE percentage_ongehuwd.xsi_nil
      REMOVE percentage_overige_niet_westerse_allochtonen
      REMOVE percentage_overige_niet_westerse_allochtonen.xsi_nil
      REMOVE percentage_uit_suriname
      REMOVE percentage_uit_suriname.xsi_nil
      REMOVE percentage_uit_turkije
      REMOVE percentage_uit_turkije.xsi_nil
      REMOVE percentage_verweduwd
      REMOVE percentage_verweduwd.xsi_nil
      REMOVE percentage_westerse_allochtonen
      REMOVE percentage_westerse_allochtonen.xsi_nil
      REMOVE meest_voorkomende_postcode
      REMOVE meest_voorkomende_postcode.xsi_nil
      REMOVE stedelijkheid_adressen_per_km2
      REMOVE stedelijkheid_adressen_per_km2.xsi_nil
      REMOVE water
      REMOVE water.xsi_nil
      REMOVE geom
      REMOVE indelingswijziging_wijken_en_buurten_indicator
      REMOVE indelingswijziging_wijken_en_buurten_indicator.xsi_nil
      RENAME_SET_VALUE wijkcode > CBS_wijkcode
      REMOVE wijkcode.xsi_nil
      RENAME_SET_VALUE wijknaam > CBS_wijknaam
      REMOVE wijknaam.xsi_nil
    -> FeatureMerger_CBSwijk [REQUESTOR]
FeatureMerger_CBSwijk
    SUPPLIERS_FIRST = No
    PROCESS_DUPS = No
    ATTR_CONFLICT_RES = Use Requestor
    REJECT_NULL_MISSING_KEYS = No
    ATTR_ACCUM_MODE = Merge Supplier
    JOIN_KEYS = @Value(CBS_wijkcode) @Value(CBS_wijkcode) AUTO
    MERGE_TYPE = Attributes Only
    IGNORE_NULLS = No
    MERGED -> PercenterenEnAfronden_CBSwijk [In]
    <REJECTED> -> Junction_5
PercenterenEnAfronden_CBSwijk
    OPP_INFRA_PARKEERVLAK._SUM = @Value(opp_infra_parkeervlak._sum)
    OPP_INFRA_OVERIG._SUM = @Value(opp_infra_overig._sum)
    OPP_INFRA_OV._SUM = @Value(opp_infra_ov._sum)
    OPP_INFRA_AUTO._SUM = @Value(opp_infra_auto._sum)
    _AREA = @Value(_area)
    OPP_WATER._SUM = @Value(opp_water._sum)
    OPP_INFRA_VLIEGVERKEER._SUM = @Value(opp_infra_vliegverkeer._sum)
    OPP_BEBOUWING._SUM = @Value(opp_bebouwing._sum)
    OPP_INFRA_FIETS._SUM = @Value(opp_infra_fiets._sum)
    OPP_INFRA_VOETGANGERS._SUM = @Value(opp_infra_voetgangers._sum)
    OPP_GROEN._SUM = @Value(opp_groen._sum)
    Uit -> AttributeCreator_peildatum_Wijk
    <Rejected> -> Junction_7
Junction_7
    -> Junction_8
Junction_8
    -> _Rejected_
Junction_5
    -> Junction_6
Junction_6
    -> _Rejected_
Tester_2
    TEST_MODE = Automatic
    TEST_CLAUSE:
      TEST @Value(gemeentecode) = GM0599
      TEST @Value(oppervlakte_land_in_ha) > 0
    TEST_DESCRIPTION = ""
    BOOL_OP = AND
    PASSED -> AttributeManager
AttributeManager
    ATTR_TABLE:
      REMOVE gml_parent_id
      REMOVE gml_parent_property
      REMOVE gml_id
      REMOVE aantal_inwoners
      REMOVE aantal_inwoners.xsi_nil
      REMOVE mannen
      REMOVE mannen.xsi_nil
      REMOVE vrouwen
      REMOVE vrouwen.xsi_nil
      REMOVE aantal_huishoudens
      REMOVE aantal_huishoudens.xsi_nil
      REMOVE bevolkingsdichtheid_inwoners_per_km2
      REMOVE bevolkingsdichtheid_inwoners_per_km2.xsi_nil
      REMOVE dekkingspercentage
      REMOVE dekkingspercentage.xsi_nil
      REMOVE gemiddelde_huishoudsgrootte
      REMOVE gemiddelde_huishoudsgrootte.xsi_nil
      RENAME_SET_VALUE gemeentecode > CBS_gemeentecode
      REMOVE gemeentecode.xsi_nil
      RENAME_SET_VALUE gemeentenaam > CBS_gemeentenaam
      REMOVE gemeentenaam.xsi_nil
      REMOVE omgevingsadressendichtheid
      REMOVE omgevingsadressendichtheid.xsi_nil
      REMOVE oppervlakte_land_in_ha
      REMOVE oppervlakte_land_in_ha.xsi_nil
      REMOVE oppervlakte_totaal_in_ha
      REMOVE oppervlakte_totaal_in_ha.xsi_nil
      REMOVE oppervlakte_water_in_ha
      REMOVE oppervlakte_water_in_ha.xsi_nil
      REMOVE percentage_personen_0_tot_15_jaar
      REMOVE percentage_personen_0_tot_15_jaar.xsi_nil
      REMOVE percentage_personen_15_tot_25_jaar
      REMOVE percentage_personen_15_tot_25_jaar.xsi_nil
      REMOVE percentage_personen_25_tot_45_jaar
      REMOVE percentage_personen_25_tot_45_jaar.xsi_nil
      REMOVE percentage_personen_45_tot_65_jaar
      REMOVE percentage_personen_45_tot_65_jaar.xsi_nil
      REMOVE percentage_personen_65_jaar_en_ouder
      REMOVE percentage_personen_65_jaar_en_ouder.xsi_nil
      REMOVE percentage_uit_nederlandse_antillen_en_aruba
      REMOVE percentage_uit_nederlandse_antillen_en_aruba.xsi_nil
      REMOVE percentage_eenpersoonshuishoudens
      REMOVE percentage_eenpersoonshuishoudens.xsi_nil
      REMOVE percentage_gehuwd
      REMOVE percentage_gehuwd.xsi_nil
      REMOVE percentage_gescheid
      REMOVE percentage_gescheid.xsi_nil
      REMOVE percentage_huishoudens_met_kinderen
      REMOVE percentage_huishoudens_met_kinderen.xsi_nil
      REMOVE percentage_huishoudens_zonder_kinderen
      REMOVE percentage_huishoudens_zonder_kinderen.xsi_nil
      REMOVE percentage_uit_marokko
      REMOVE percentage_uit_marokko.xsi_nil
      REMOVE percentage_niet_westerse_allochtonen
      REMOVE percentage_niet_westerse_allochtonen.xsi_nil
      REMOVE percentage_ongehuwd
      REMOVE percentage_ongehuwd.xsi_nil
      REMOVE percentage_overige_niet_westerse_allochtonen
      REMOVE percentage_overige_niet_westerse_allochtonen.xsi_nil
      REMOVE percentage_uit_suriname
      REMOVE percentage_uit_suriname.xsi_nil
      REMOVE percentage_uit_turkije
      REMOVE percentage_uit_turkije.xsi_nil
      REMOVE percentage_verweduwd
      REMOVE percentage_verweduwd.xsi_nil
      REMOVE percentage_westerse_allochtonen
      REMOVE percentage_westerse_allochtonen.xsi_nil
      REMOVE meest_voorkomende_postcode
      REMOVE meest_voorkomende_postcode.xsi_nil
      REMOVE stedelijkheid_adressen_per_km2
      REMOVE stedelijkheid_adressen_per_km2.xsi_nil
      REMOVE water
      REMOVE water.xsi_nil
      REMOVE geom
    -> FeatureMerger_CBSgemeente [REQUESTOR]
FeatureMerger_CBSgemeente
    SUPPLIERS_FIRST = No
    PROCESS_DUPS = No
    ATTR_CONFLICT_RES = Use Requestor
    REJECT_NULL_MISSING_KEYS = No
    ATTR_ACCUM_MODE = Merge Supplier
    JOIN_KEYS = @Value(CBS_gemeentecode) @Value(CBS_gemeentecode) AUTO
    MERGE_TYPE = Attributes Only
    IGNORE_NULLS = No
    MERGED -> PercenterenEnAfronden_CBSgemeente [In]
    <REJECTED> -> Junction
PercenterenEnAfronden_CBSgemeente
    OPP_INFRA_PARKEERVLAK._SUM = @Value(opp_infra_parkeervlak._sum)
    OPP_INFRA_OVERIG._SUM = @Value(opp_infra_overig._sum)
    OPP_INFRA_OV._SUM = @Value(opp_infra_ov._sum)
    OPP_INFRA_AUTO._SUM = @Value(opp_infra_auto._sum)
    _AREA = @Value(_area)
    OPP_WATER._SUM = @Value(opp_water._sum)
    OPP_INFRA_VLIEGVERKEER._SUM = @Value(opp_infra_vliegverkeer._sum)
    OPP_BEBOUWING._SUM = @Value(opp_bebouwing._sum)
    OPP_INFRA_FIETS._SUM = @Value(opp_infra_fiets._sum)
    OPP_INFRA_VOETGANGERS._SUM = @Value(opp_infra_voetgangers._sum)
    OPP_GROEN._SUM = @Value(opp_groen._sum)
    Uit -> AttributeCreator_peildatum_Gemeente
    <Rejected> -> Junction_3
Junction_3
    -> Junction_4
Junction_4
    -> _Rejected_
Junction
    -> Junction_2
Junction_2
    -> _Rejected_
_Rejected_: Logger
    MAXFEATS = 20
    MESSAGE = Feature is:
    MAXCOORDS = 20

Bookmark: BGT Rotterdam K:\Geo
  BGT_Vlakken: BGT_Gemeente 
  WHERE NIVO = 0 AND KLASSE_IMG NOT IN ('Ongeclassificeerd object','Vegetatieobject','Weginrichtingselement')
BGT_Vlakken (reader GEODATABASE_FILE_1)
    attributes: OBJECTID integer, KLASSE char(35), EIGENAAR char(70), GIDS_ID double, DGDT_ID double, CODE double, CODE_OMS char(50), MULTICODE double, MC_OMS_1 char(50), MC_OMS_2 char(50), MC_OMS_3 char(50), HERKOMST char(20), STATUS char(25), NIVO double, INWIN char(10), LAAG char(20), BEHEERDER char(70), BRONHOUDER char(70), FUNCTIE char(70), FUNCTIEPL char(70), FYSIEKVK char(70), FYSIEKVKPL char(70), HMAAND char(70), HOORTBIJ double, IDBAG char(70), IDBAG_OPR char(70), INONDERZ double, KLASSE_IMG char(70), KRUINLIJN char(38), LVPUBLDTM char(10),
      OPTALUD double, OVERBRBEW char(70), TEKST char(70), TYPE char(70), TYPEPL char(70), SHAPE_Length double, SHAPE_Area double
    -> AttributeFilter_BGT_KLASSE_IMG

Bookmark: CBS Wijken en Buurten 2017 WFS
  http://www.nationaalgeoregister.nl/geonetwork/srv/dut/catalog.search#/metadata/dcb7f0d7-d70b-4eab-9a46-7af98de860bd?tab=contact
cbs_buurten_2017 (reader WFS_3)
    attributes: gml_parent_id xml_buffer, gml_parent_property xml_buffer, gml_id xml_buffer, aantal_inwoners xml_real64, aantal_inwoners.xsi_nil xml_boolean, mannen xml_real64, mannen.xsi_nil xml_boolean, vrouwen xml_real64, vrouwen.xsi_nil xml_boolean, aantal_huishoudens xml_real64, aantal_huishoudens.xsi_nil xml_boolean, bevolkingsdichtheid_inwoners_per_km2 xml_real64, bevolkingsdichtheid_inwoners_per_km2.xsi_nil xml_boolean, buurtcode xml_buffer, buurtcode.xsi_nil xml_boolean, buurtnaam xml_buffer, buurtnaam.xsi_nil xml_boolean, dekkingspercentage xml_real64, dekkingspercentage.xsi_nil xml_boolean, gemiddelde_huishoudsgrootte xml_real64, gemiddelde_huishoudsgrootte.xsi_nil xml_boolean, gemeentecode xml_buffer, gemeentecode.xsi_nil xml_boolean, gemeentenaam xml_buffer, gemeentenaam.xsi_nil xml_boolean, indelingswijziging_wijken_en_buurten_indicator xml_real64, indelingswijziging_wijken_en_buurten_indicator.xsi_nil xml_boolean, omgevingsadressendichtheid xml_real64, omgevingsadressendichtheid.xsi_nil xml_boolean, oppervlakte_land_in_ha xml_real64,
      oppervlakte_land_in_ha.xsi_nil xml_boolean, oppervlakte_totaal_in_ha xml_real64, oppervlakte_totaal_in_ha.xsi_nil xml_boolean, oppervlakte_water_in_ha xml_real64, oppervlakte_water_in_ha.xsi_nil xml_boolean, percentage_personen_0_tot_15_jaar xml_real64, percentage_personen_0_tot_15_jaar.xsi_nil xml_boolean, percentage_personen_15_tot_25_jaar xml_real64, percentage_personen_15_tot_25_jaar.xsi_nil xml_boolean, percentage_personen_25_tot_45_jaar xml_real64, percentage_personen_25_tot_45_jaar.xsi_nil xml_boolean, percentage_personen_45_tot_65_jaar xml_real64, percentage_personen_45_tot_65_jaar.xsi_nil xml_boolean, percentage_personen_65_jaar_en_ouder xml_real64, percentage_personen_65_jaar_en_ouder.xsi_nil xml_boolean, percentage_uit_nederlandse_antillen_en_aruba xml_real64, percentage_uit_nederlandse_antillen_en_aruba.xsi_nil xml_boolean, percentage_eenpersoonshuishoudens xml_real64, percentage_eenpersoonshuishoudens.xsi_nil xml_boolean, percentage_gehuwd xml_real64, percentage_gehuwd.xsi_nil xml_boolean, percentage_gescheid xml_real64, percentage_gescheid.xsi_nil xml_boolean, percentage_huishoudens_met_kinderen xml_real64, percentage_huishoudens_met_kinderen.xsi_nil xml_boolean, percentage_huishoudens_zonder_kinderen xml_real64, percentage_huishoudens_zonder_kinderen.xsi_nil xml_boolean, percentage_uit_marokko xml_real64, percentage_uit_marokko.xsi_nil xml_boolean, percentage_niet_westerse_allochtonen xml_real64,
      percentage_niet_westerse_allochtonen.xsi_nil xml_boolean, percentage_ongehuwd xml_real64, percentage_ongehuwd.xsi_nil xml_boolean, percentage_overige_niet_westerse_allochtonen xml_real64, percentage_overige_niet_westerse_allochtonen.xsi_nil xml_boolean, percentage_uit_suriname xml_real64, percentage_uit_suriname.xsi_nil xml_boolean, percentage_uit_turkije xml_real64, percentage_uit_turkije.xsi_nil xml_boolean, percentage_verweduwd xml_real64, percentage_verweduwd.xsi_nil xml_boolean, percentage_westerse_allochtonen xml_real64, percentage_westerse_allochtonen.xsi_nil xml_boolean, meest_voorkomende_postcode xml_real64, meest_voorkomende_postcode.xsi_nil xml_boolean, stedelijkheid_adressen_per_km2 xml_real64, stedelijkheid_adressen_per_km2.xsi_nil xml_boolean, water xml_buffer, water.xsi_nil xml_boolean, wijkcode xml_buffer, wijkcode.xsi_nil xml_boolean, geom xml_geometry
    -> Tester_4
cbs_wijken_2017 (reader WFS_2)
    attributes: gml_parent_id xml_buffer, gml_parent_property xml_buffer, gml_id xml_buffer, aantal_inwoners xml_real64, aantal_inwoners.xsi_nil xml_boolean, mannen xml_real64, mannen.xsi_nil xml_boolean, vrouwen xml_real64, vrouwen.xsi_nil xml_boolean, aantal_huishoudens xml_real64, aantal_huishoudens.xsi_nil xml_boolean, bevolkingsdichtheid_inwoners_per_km2 xml_real64, bevolkingsdichtheid_inwoners_per_km2.xsi_nil xml_boolean, dekkingspercentage xml_real64, dekkingspercentage.xsi_nil xml_boolean, gemiddelde_huishoudsgrootte xml_real64, gemiddelde_huishoudsgrootte.xsi_nil xml_boolean, gemeentecode xml_buffer, gemeentecode.xsi_nil xml_boolean, gemeentenaam xml_buffer, gemeentenaam.xsi_nil xml_boolean, indelingswijziging_wijken_en_buurten_indicator xml_real64, indelingswijziging_wijken_en_buurten_indicator.xsi_nil xml_boolean, omgevingsadressendichtheid xml_real64, omgevingsadressendichtheid.xsi_nil xml_boolean, oppervlakte_land_in_ha xml_real64, oppervlakte_land_in_ha.xsi_nil xml_boolean, oppervlakte_totaal_in_ha xml_real64, oppervlakte_totaal_in_ha.xsi_nil xml_boolean, oppervlakte_water_in_ha xml_real64,
      oppervlakte_water_in_ha.xsi_nil xml_boolean, percentage_personen_0_tot_15_jaar xml_real64, percentage_personen_0_tot_15_jaar.xsi_nil xml_boolean, percentage_personen_15_tot_25_jaar xml_real64, percentage_personen_15_tot_25_jaar.xsi_nil xml_boolean, percentage_personen_25_tot_45_jaar xml_real64, percentage_personen_25_tot_45_jaar.xsi_nil xml_boolean, percentage_personen_45_tot_65_jaar xml_real64, percentage_personen_45_tot_65_jaar.xsi_nil xml_boolean, percentage_personen_65_jaar_en_ouder xml_real64, percentage_personen_65_jaar_en_ouder.xsi_nil xml_boolean, percentage_uit_nederlandse_antillen_en_aruba xml_real64, percentage_uit_nederlandse_antillen_en_aruba.xsi_nil xml_boolean, percentage_eenpersoonshuishoudens xml_real64, percentage_eenpersoonshuishoudens.xsi_nil xml_boolean, percentage_gehuwd xml_real64, percentage_gehuwd.xsi_nil xml_boolean, percentage_gescheid xml_real64, percentage_gescheid.xsi_nil xml_boolean, percentage_huishoudens_met_kinderen xml_real64, percentage_huishoudens_met_kinderen.xsi_nil xml_boolean, percentage_huishoudens_zonder_kinderen xml_real64, percentage_huishoudens_zonder_kinderen.xsi_nil xml_boolean, percentage_uit_marokko xml_real64, percentage_uit_marokko.xsi_nil xml_boolean, percentage_niet_westerse_allochtonen xml_real64, percentage_niet_westerse_allochtonen.xsi_nil xml_boolean, percentage_ongehuwd xml_real64, percentage_ongehuwd.xsi_nil xml_boolean, percentage_overige_niet_westerse_allochtonen xml_real64,
      percentage_overige_niet_westerse_allochtonen.xsi_nil xml_boolean, percentage_uit_suriname xml_real64, percentage_uit_suriname.xsi_nil xml_boolean, percentage_uit_turkije xml_real64, percentage_uit_turkije.xsi_nil xml_boolean, percentage_verweduwd xml_real64, percentage_verweduwd.xsi_nil xml_boolean, percentage_westerse_allochtonen xml_real64, percentage_westerse_allochtonen.xsi_nil xml_boolean, meest_voorkomende_postcode xml_real64, meest_voorkomende_postcode.xsi_nil xml_boolean, stedelijkheid_adressen_per_km2 xml_real64, stedelijkheid_adressen_per_km2.xsi_nil xml_boolean, water xml_buffer, water.xsi_nil xml_boolean, wijkcode xml_buffer, wijkcode.xsi_nil xml_boolean, wijknaam xml_buffer, wijknaam.xsi_nil xml_boolean, geom xml_geometry
    -> Tester_3
gemeenten2017 (reader WFS_1)
    attributes: gml_parent_id xml_buffer, gml_parent_property xml_buffer, gml_id xml_buffer, aantal_inwoners xml_real64, aantal_inwoners.xsi_nil xml_boolean, mannen xml_real64, mannen.xsi_nil xml_boolean, vrouwen xml_real64, vrouwen.xsi_nil xml_boolean, aantal_huishoudens xml_real64, aantal_huishoudens.xsi_nil xml_boolean, bevolkingsdichtheid_inwoners_per_km2 xml_real64, bevolkingsdichtheid_inwoners_per_km2.xsi_nil xml_boolean, dekkingspercentage xml_real64, dekkingspercentage.xsi_nil xml_boolean, gemiddelde_huishoudsgrootte xml_real64, gemiddelde_huishoudsgrootte.xsi_nil xml_boolean, gemeentecode xml_buffer, gemeentecode.xsi_nil xml_boolean, gemeentenaam xml_buffer, gemeentenaam.xsi_nil xml_boolean, omgevingsadressendichtheid xml_real64, omgevingsadressendichtheid.xsi_nil xml_boolean, oppervlakte_land_in_ha xml_real64, oppervlakte_land_in_ha.xsi_nil xml_boolean, oppervlakte_totaal_in_ha xml_real64, oppervlakte_totaal_in_ha.xsi_nil xml_boolean, oppervlakte_water_in_ha xml_real64, oppervlakte_water_in_ha.xsi_nil xml_boolean, percentage_personen_0_tot_15_jaar xml_real64,
      percentage_personen_0_tot_15_jaar.xsi_nil xml_boolean, percentage_personen_15_tot_25_jaar xml_real64, percentage_personen_15_tot_25_jaar.xsi_nil xml_boolean, percentage_personen_25_tot_45_jaar xml_real64, percentage_personen_25_tot_45_jaar.xsi_nil xml_boolean, percentage_personen_45_tot_65_jaar xml_real64, percentage_personen_45_tot_65_jaar.xsi_nil xml_boolean, percentage_personen_65_jaar_en_ouder xml_real64, percentage_personen_65_jaar_en_ouder.xsi_nil xml_boolean, percentage_uit_nederlandse_antillen_en_aruba xml_real64, percentage_uit_nederlandse_antillen_en_aruba.xsi_nil xml_boolean, percentage_eenpersoonshuishoudens xml_real64, percentage_eenpersoonshuishoudens.xsi_nil xml_boolean, percentage_gehuwd xml_real64, percentage_gehuwd.xsi_nil xml_boolean, percentage_gescheid xml_real64, percentage_gescheid.xsi_nil xml_boolean, percentage_huishoudens_met_kinderen xml_real64, percentage_huishoudens_met_kinderen.xsi_nil xml_boolean, percentage_huishoudens_zonder_kinderen xml_real64, percentage_huishoudens_zonder_kinderen.xsi_nil xml_boolean, percentage_uit_marokko xml_real64, percentage_uit_marokko.xsi_nil xml_boolean, percentage_niet_westerse_allochtonen xml_real64, percentage_niet_westerse_allochtonen.xsi_nil xml_boolean, percentage_ongehuwd xml_real64, percentage_ongehuwd.xsi_nil xml_boolean, percentage_overige_niet_westerse_allochtonen xml_real64, percentage_overige_niet_westerse_allochtonen.xsi_nil xml_boolean, percentage_uit_suriname xml_real64,
      percentage_uit_suriname.xsi_nil xml_boolean, percentage_uit_turkije xml_real64, percentage_uit_turkije.xsi_nil xml_boolean, percentage_verweduwd xml_real64, percentage_verweduwd.xsi_nil xml_boolean, percentage_westerse_allochtonen xml_real64, percentage_westerse_allochtonen.xsi_nil xml_boolean, meest_voorkomende_postcode xml_real64, meest_voorkomende_postcode.xsi_nil xml_boolean, stedelijkheid_adressen_per_km2 xml_real64, stedelijkheid_adressen_per_km2.xsi_nil xml_boolean, water xml_buffer, water.xsi_nil xml_boolean, geom xml_geometry
    -> Tester_2

Bookmark: Toevoegen van metadata
Note: peildatum toevoegen
AttributeCreator_peildatum_Buurt
    ATTR_TABLE = SET_TO peildatum = $(P_PEILDATUM)
    -> AttributeCreator_Buurt_actueel
Note: ind_actueel op true / zetten
AttributeCreator_Buurt_actueel
    ATTR_TABLE = SET_TO ind_actueel = 1
    -> UUIDGenerator_Buurt
Note: genereren van een unieke sleutel
UUIDGenerator_Buurt
    UUID_ATTR = UUID
    -> Functieverdeling_per_CBS_buurt (writer GEODATABASE_FILE_2)
    -> Functieverdeling_per_CBS_buurt (writer GEOPACKAGE_1)

Bookmark: OGC Geopackage
Functieverdeling_per_CBS_buurt (writer GEOPACKAGE_1)
    attributes: UUID text(36), CBS_buurtnaam text, CBS_buurtcode text(10), CBS_wijkcode text(8), CBS_gemeentecode text(6), CBS_gemeentenaam text, perc_groen float, perc_bebouwing float, perc_water float, perc_infra_overig float, perc_infra_auto float, perc_infra_ov float, perc_infra_fiets float, perc_infra_voetgangers float, perc_infra_parkeervlak float, perc_infra_vliegverkeer float, opp_gebied_ha float, opp_groen_ha float, opp_bebouwing_ha float, opp_water_ha float, opp_infra_overig_ha float, opp_infra_auto_ha float, opp_infra_ov_ha float, opp_infra_fiets_ha float, opp_infra_voetgangers_ha float, opp_infra_parkeervlak_ha float, opp_infra_vliegverkeer_ha float, peildatum smallint, ind_actueel boolean
Functieverdeling_per_CBS_wijk (writer GEOPACKAGE_1)
    attributes: UUID text(36), CBS_wijkcode text(8), CBS_wijknaam text, CBS_gemeentecode text(6), CBS_gemeentenaam text, peildatum smallint, ind_actueel boolean, opp_bebouwing_ha float, opp_gebied_ha float, opp_groen_ha float, opp_infra_auto_ha float, opp_infra_fiets_ha float, opp_infra_ov_ha float, opp_infra_overig_ha float, opp_infra_parkeervlak_ha float, opp_infra_vliegverkeer_ha float, opp_infra_voetgangers_ha float, opp_water_ha float, perc_bebouwing float, perc_groen float, perc_infra_auto float, perc_infra_fiets float, perc_infra_ov float, perc_infra_overig float, perc_infra_parkeervlak float, perc_infra_vliegverkeer float, perc_infra_voetgangers float, perc_water float
Functieverdeling_per_CBS_gemeente (writer GEOPACKAGE_1)
    attributes: UUID text(36), CBS_gemeentecode text(6), CBS_gemeentenaam text, peildatum smallint, ind_actueel boolean, opp_bebouwing_ha float, opp_gebied_ha float, opp_groen_ha float, opp_infra_auto_ha float, opp_infra_fiets_ha float, opp_infra_ov_ha float, opp_infra_overig_ha float, opp_infra_parkeervlak_ha float, opp_infra_vliegverkeer_ha float, opp_infra_voetgangers_ha float, opp_water_ha float, perc_bebouwing float, perc_groen float, perc_infra_auto float, perc_infra_fiets float, perc_infra_ov float, perc_infra_overig float, perc_infra_parkeervlak float, perc_infra_vliegverkeer float, perc_infra_voetgangers float, perc_water float

Bookmark: ESRI File Geodatabase
Functieverdeling_per_CBS_buurt (writer GEODATABASE_FILE_2)
    attributes: UUID char(36), CBS_buurtnaam char(255), CBS_buurtcode char(10), CBS_wijkcode char(8), CBS_gemeentecode char(6), CBS_gemeentenaam char(255), peildatum smallint, ind_actueel boolean, opp_bebouwing_ha float, opp_gebied_ha float, opp_groen_ha float, opp_infra_auto_ha float, opp_infra_fiets_ha float, opp_infra_ov_ha float, opp_infra_overig_ha float, opp_infra_parkeervlak_ha float, opp_infra_vliegverkeer_ha float, opp_infra_voetgangers_ha float, opp_water_ha float, perc_bebouwing float, perc_groen float, perc_infra_auto float, perc_infra_fiets float, perc_infra_ov float, perc_infra_overig float, perc_infra_parkeervlak float, perc_infra_vliegverkeer float, perc_infra_voetgangers float, perc_water float
Functieverdeling_per_CBS_wijk (writer GEODATABASE_FILE_2)
    attributes: UUID char(36), CBS_wijkcode char(8), CBS_wijknaam char(255), CBS_gemeentecode char(6), CBS_gemeentenaam char(255), peildatum smallint, ind_actueel boolean, opp_bebouwing_ha float, opp_gebied_ha float, opp_groen_ha float, opp_infra_auto_ha float, opp_infra_fiets_ha float, opp_infra_ov_ha float, opp_infra_overig_ha float, opp_infra_parkeervlak_ha float, opp_infra_vliegverkeer_ha float, opp_infra_voetgangers_ha float, opp_water_ha float, perc_bebouwing float, perc_groen float, perc_infra_auto float, perc_infra_fiets float, perc_infra_ov float, perc_infra_overig float, perc_infra_parkeervlak float, perc_infra_vliegverkeer float, perc_infra_voetgangers float, perc_water float
Functieverdeling_per_CBS_gemeente (writer GEODATABASE_FILE_2)
    attributes: UUID char(36), CBS_gemeentecode char(6), CBS_gemeentenaam char(255), peildatum smallint, ind_actueel boolean, opp_bebouwing_ha float, opp_gebied_ha float, opp_groen_ha float, opp_infra_auto_ha float, opp_infra_fiets_ha float, opp_infra_ov_ha float, opp_infra_overig_ha float, opp_infra_parkeervlak_ha float, opp_infra_vliegverkeer_ha float, opp_infra_voetgangers_ha float, opp_water_ha float, perc_bebouwing float, perc_groen float, perc_infra_auto float, perc_infra_fiets float, perc_infra_ov float, perc_infra_overig float, perc_infra_parkeervlak float, perc_infra_vliegverkeer float, perc_infra_voetgangers float, perc_water float

Bookmark: Toevoegen van metadata
Note: peildatum toevoegen
AttributeCreator_peildatum_Wijk
    ATTR_TABLE = SET_TO peildatum = $(P_PEILDATUM)
    -> AttributeCreator_Wijk_actueel
Note: ind_actueel op true / zetten
AttributeCreator_Wijk_actueel
    ATTR_TABLE = SET_TO ind_actueel = 1
    -> UUIDGenerator_Wijk
Note: genereren van een unieke sleutel
UUIDGenerator_Wijk
    UUID_ATTR = UUID
    -> Functieverdeling_per_CBS_wijk (writer GEOPACKAGE_1)
    -> Functieverdeling_per_CBS_wijk (writer GEODATABASE_FILE_2)

Bookmark: Toevoegen van metadata
Note: peildatum toevoegen
AttributeCreator_peildatum_Gemeente
    ATTR_TABLE = SET_TO peildatum = $(P_PEILDATUM)
    -> AttributeCreator_Gemeente_actueel
Note: ind_actueel op true / zetten
AttributeCreator_Gemeente_actueel
    ATTR_TABLE = SET_TO ind_actueel = 1
    -> UUIDGenerator_Gemeente
Note: genereren van een unieke sleutel
UUIDGenerator_Gemeente
    UUID_ATTR = UUID
    -> Functieverdeling_per_CBS_gemeente (writer GEODATABASE_FILE_2)
    -> Functieverdeling_per_CBS_gemeente (writer GEOPACKAGE_1)

FME custom transformer PercenterenEnAfronden

Parameters:
- OPP_INFRA_OVERIG._SUM = @Value(opp_infra_overig._sum)   # Opp Infra Overig. Sum
- OPP_INFRA_FIETS._SUM = @Value(opp_infra_fiets._sum)   # Opp Infra Fiets. Sum
- OPP_INFRA_VLIEGVERKEER._SUM = @Value(opp_infra_vliegverkeer._sum)   # Opp Infra Vliegverkeer. Sum
- OPP_INFRA_VOETGANGERS._SUM = @Value(opp_infra_voetgangers._sum)   # Opp Infra Voetgangers. Sum
- _AREA = @Value(_area)   # Area
- OPP_INFRA_PARKEERVLAK._SUM = @Value(opp_infra_parkeervlak._sum)   # Opp Infra Parkeervlak. Sum
- OPP_GROEN._SUM = @Value(opp_groen._sum)   # Opp Groen. Sum
- OPP_INFRA_OV._SUM = @Value(opp_infra_ov._sum)   # Opp Infra Ov. Sum
- OPP_WATER._SUM = @Value(opp_water._sum)   # Opp Water. Sum
- OPP_INFRA_AUTO._SUM = @Value(opp_infra_auto._sum)   # Opp Infra Auto. Sum
- OPP_BEBOUWING._SUM = @Value(opp_bebouwing._sum)   # Opp Bebouwing. Sum

In (input)
    -> AttributeCreator_5
AttributeCreator_5
    ATTR_TABLE:
      SET_TO perc_groen = @Evaluate((@Value(opp_groen._sum)/@Value(_area))*100)
      SET_TO perc_bebouwing = @Evaluate((@Value(opp_bebouwing._sum)/@Value(_area))*100)
      SET_TO perc_water = @Evaluate((@Value(opp_water._sum)/@Value(_area))*100)
      SET_TO perc_infra_overig = @Evaluate((@Value(opp_infra_overig._sum)/@Value(_area))*100)
      SET_TO perc_infra_auto = @Evaluate((@Value(opp_infra_auto._sum)/@Value(_area))*100)
      SET_TO perc_infra_ov = @Evaluate((@Value(opp_infra_ov._sum)/@Value(_area))*100)
      SET_TO perc_infra_fiets = @Evaluate((@Value(opp_infra_fiets._sum)/@Value(_area))*100)
      SET_TO perc_infra_voetgangers = @Evaluate((@Value(opp_infra_voetgangers._sum)/@Value(_area))*100)
      SET_TO perc_infra_parkeervlak = @Evaluate((@Value(opp_infra_parkeervlak._sum)/@Value(_area))*100)
      SET_TO perc_infra_vliegverkeer = @Evaluate((@Value(opp_infra_vliegverkeer._sum)/@Value(_area))*100)
    -> AttributeManager_9
AttributeManager_9
    ATTR_TABLE:
      RENAME_SET_VALUE _area > opp_gebied_ha = @Evaluate(@Value(opp_gebied_ha)/10000)
      RENAME_SET_VALUE opp_groen._sum > opp_groen_ha = @Evaluate(@Value(opp_groen_ha)/10000)
      RENAME_SET_VALUE opp_infra_auto._sum > opp_infra_auto_ha = @Evaluate(@Value(opp_infra_auto_ha)/10000)
      RENAME_SET_VALUE opp_infra_fiets._sum > opp_infra_fiets_ha = @Evaluate(@Value(opp_infra_fiets_ha)/10000)
      RENAME_SET_VALUE opp_infra_vliegverkeer._sum > opp_infra_vliegverkeer_ha = @Evaluate(@Value(opp_infra_vliegverkeer_ha)/10000)
      RENAME_SET_VALUE opp_water._sum > opp_water_ha = @Evaluate(@Value(opp_water_ha)/10000)
      RENAME_SET_VALUE opp_bebouwing._sum > opp_bebouwing_ha = @Evaluate(@Value(opp_bebouwing_ha)/10000)
      RENAME_SET_VALUE opp_infra_ov._sum > opp_infra_ov_ha = @Evaluate(@Value(opp_infra_ov_ha)/10000)
      RENAME_SET_VALUE opp_infra_overig._sum > opp_infra_overig_ha = @Evaluate(@Value(opp_infra_overig_ha)/10000)
      RENAME_SET_VALUE opp_infra_parkeervlak._sum > opp_infra_parkeervlak_ha = @Evaluate(@Value(opp_infra_parkeervlak_ha)/10000)
      RENAME_SET_VALUE opp_infra_voetgangers._sum > opp_infra_voetgangers_ha = @Evaluate(@Value(opp_infra_voetgangers_ha)/10000)
    -> AttributeRounder_CBSbuurt_opp
AttributeRounder_CBSbuurt_opp
    ROUND_TYPE = Nearest
    PLACES = 2
    SRC_ATTRS = opp_infra_voetgangers_ha opp_infra_ov_ha opp_infra_fiets_ha opp_infra_overig_ha opp_gebied_ha opp_infra_parkeervlak_ha opp_water_ha opp_infra_auto_ha opp_infra_vliegverkeer_ha opp_groen_ha opp_bebouwing_ha
    -> AttributeRounder_CBSbuurt_perc
    <REJECTED> -> <Rejected> (output)
AttributeRounder_CBSbuurt_perc
    ROUND_TYPE = Nearest
    PLACES = 1
    SRC_ATTRS = perc_bebouwing perc_infra_overig perc_infra_parkeervlak perc_water perc_infra_fiets perc_infra_auto perc_infra_ov perc_groen perc_infra_voetgangers perc_infra_vliegverkeer
    -> Uit (output)
    <REJECTED> -> <Rejected> (output)
Uit (output)
<Rejected> (output)
